Imports Inventor.UnitsTypeEnum
Dim oPartDoc As Document
oPartDoc = ThisDoc.Document
If oPartDoc.DocumentType = kPartDocumentObject Then

Dim oPartCompDef As PartComponentDefinition
oPartCompDef = oPartDoc.ComponentDefinition

Dim oParams As Parameters
oParams=oPartCompDef.Parameters
Dim oUserParams As UserParameters
oUserParams=oParams.UserParameters
Dim oAwesomeParameter As Parameter
Try
otester = oUserParams.Item("Verkoper")
Catch
oInsulationType=oUserParams.AddByValue("Verkoper", "Gerrit Ver Eecke", kTextUnits)
MultiValue.SetList("Verkoper", "Gerrit Ver Eecke", "Jean-Paul van der Heiden", "Karel Claes")
End Try
End If
Parameter.Param("Verkoper").ExposedAsProperty = False
Parameter.Param("Verkoper").IsKey = True
