iProperties.Value("Custom", "Volume") = Round(iProperties.Volume / 1000000  , 1 "liter")
iProperties.Value("Custom", "Mass") = Round(iProperties.Mass / 1  "kg" , 3 "kg")
MessageBox.Show(Round(iProperties.Mass / 1   "kg" , 1 "kg") & " kg", "Mass of Model in Kilograms")
