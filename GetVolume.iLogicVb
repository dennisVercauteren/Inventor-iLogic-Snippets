iProperties.Value("Custom", "Volume") = Round(iProperties.Volume / 1000000  , 1 "liter")
iProperties.Value("Custom", "Mass") = Round(iProperties.Mass / 1 "kg" , 3 "kg")
iProperties.Value("Custom", "Volgnummer") = "00"
