oDate = DateTime.Now.ToString("yyyy-MM-dd")
oThisPath = ThisDoc.WorkspacePath()
oPubFolder = Left(oThisPath, InStrRev(oThisPath, "\",)) 
oPublicationLoc = oPubFolder & "Werkboek CAD" & "\" & "Publicatie" & "\" & oDate & "\"
iProperties.Value("Custom", "Publocation") = oPublicationLoc

oPath = ThisDoc.WorkspacePath() & "/" & "Master tekeningen" & ".pdf"
oPartnumber = iProperties.Value("Project", "Part Number")
oProjectnumber = iProperties.Value("Project", "Project")
oRevision = iProperties.Value("Project", "Revision Number")
oFileName = ThisDoc.FileName(False) 'without extension
oPDFAddIn = ThisApplication.ApplicationAddIns.ItemById _
("{0AC6FD96-2F4D-42CE-8BE0-8AEA580399E4}")
oDocument = ThisApplication.ActiveDocument
oDate = DateTime.Now.ToString("yyyy-MM-dd")
oContext = ThisApplication.TransientObjects.CreateTranslationContext
oContext.Type = IOMechanismEnum.kFileBrowseIOMechanism
oOptions = ThisApplication.TransientObjects.CreateNameValueMap
oDataMedium = ThisApplication.TransientObjects.CreateDataMedium
iProperties.Value("Custom", "Material") = "A2"
iProperties.Value("Custom", "Finishing") = "2"
iProperties.Value("Custom", "Leverancier") = "Raes"

iLogicVb.RunExternalRule("saveasdwgpdf")

oPathWorkspace = ThisDoc.WorkspacePath()
oFolder = Left(oPathWorkspace, InStrRev(oPath, "\",)) 
oPublication = oFolder & "Werkboek CAD" & "\" & "Publicatie" & "\" & oDate & "\"


'------end of iLogic-------


doc = ThisDoc.Document
customPropertySet = doc.PropertySets.Item("Inventor User Defined Properties")
modeldocname = IO.Path.GetFileName(ThisDoc.ModelDocument.FullFileName)
mass = iProperties.Mass(modeldocname)
iProperties.Value("Custom", "Mass") = Round(mass,2) & " kg"
InventorVb.DocumentUpdate()

'------- start of iLogic code -------------------

 ' Start Outlook.
 ' If it is already running, you'll use the same instance...
   Dim oOApp
   oOApp = CreateObject("Outlook.Application")
   
' Log on. Doesn't hurt if you are already running and logged on...
   Dim olNs
   olNs = oOApp.GetNamespace("MAPI")
   olNs.Logon

'get the Inventor user name from the Inventor Options
myName= ThisApplication.GeneralOptions.UserName

'get current time
oTime = Now.ToShortTimeString

'set status tag to For Review and time stamp
iProperties.Value("Status", "Status") = "For Review @ " &  oTime

'set the Design State to Pending
iProperties.Value("Status", "Design State") = "Pending"

'set the Checked By to user name from the Inventor Options
iProperties.Value("Status", "Checked By") = myName

'set the Checked Date to the current date
iProperties.Value("Status", "Checked Date") = Now

'save the file
ThisDoc.Save

'send email using outlook
Dim oOMail

oOMail = oOApp.CreateItem(olMailItem)

With oOMail
            'replace with your client's email address
            .To = "Steven Der Kinderen <Steven.DerKinderen@azo.com>"
            .Subject = "Aanvraag materiaalnummer: " & iProperties.Value("Project", "Part Number") &" - "&  "Project:" & iProperties.Value("Project", "Project") &" - "& iProperties.Value("Summary", "Company") &" - Onderwerp: "& iProperties.Value("Summary", "Subject")
          	.Body = 	"Beste ," & iProperties.Value("Status", "Eng. Approved By") 
			.Body = .Body & "Zou je een materiaalnummer willen aanmaken voor " & iProperties.Value("Project", "Part Number") & " ."
            .Body = .Body 
			.Body = .Body & "Je kan tekeningnummer " & iProperties.Value("Project", "Part Number") & " vinden onder: " 
			.Body = .Body & iProperties.Value("Custom", "Publocation")
			.Body = .Body & "Omschrijving : " & iProperties.Value("Summary", "Subject")
			.Body = .Body & "Taal Omschrijving : Nederlands"
			.Body = .Body & "Werkstoff : " & iProperties.Value("Custom", "Material")
			.Body = .Body & "Afwerking : " & iProperties.Value("Custom", "Finishing")
			.Body = .Body & "Gewicht netto : " & iProperties.Value("Custom", "Mass")
			.Body = .Body & "Gewicht Bruto: - " 
			.Body = .Body & "Productie doorlooptijd: 7 dagen" 
			.Body = .Body & "Tekeningnummer: " & iProperties.Value("Project", "Part Number")	
			.Body = .Body & "Leverancier: " & iProperties.Value("Custom", "Leverancier")	
			.Body = .Body & "Aankoop eenheidsprijs: 300 euro"	
			.Body = .Body & "Projectleider: " & iProperties.Value("Status", "Eng. Approved By")	
			.Body = .Body & " "
			.Body = .Body & " "
			.Body = .Body & "Zou je ook de dwg willen uploaden in SAP ?"
			.Body = .Body & "Zo krijgt Raes deze mee tijdens te bestelling."
			.Body = .Body & "Bedankt,"
			.Body = .Body & " "
			
			.Body = .Body & myname
            .Display


End With
'------- end of iLogic code -------------------
